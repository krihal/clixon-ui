module junos-rpc-system {
    namespace "http://example.net/demo/junos-rpc/system";
    prefix jrs;

    revision 2024-01-01 {
        description "Demo RPCs of the Junos device: system.";
    }

    rpc get-system-information {
        description "Show hostname, model and Junos version";
        input {
            leaf brief {
                type empty;
            }
        }
    }

    rpc request-system-reboot {
        description "Reboot the device";
        input {
            leaf in {
                type string;
            }
        }
    }
}
