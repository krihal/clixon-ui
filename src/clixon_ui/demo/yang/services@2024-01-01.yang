module services {
    namespace "http://clicon.org/customer";
    prefix customer;

    import ietf-inet-types { prefix inet; }
    import clixon-controller { prefix ctrl; }

    revision "2024-01-01" {
	description "Initial revision.";
    }

    augment /ctrl:services/properties {
	list customer {
	    key "customer";

	    leaf customer {
		type string;
	    }

	    leaf-list interface {
		type string;
	    }

	    list router {
		key "router-name";

		leaf router-name {
		    type string;
		}

		list interface {
		    key "interface-name";

		    leaf interface-name {
			type string;
		    }
		}
	    }
	}
    }

    augment /ctrl:services {
	list customer {
	    key "customer-name";

	    leaf customer-name {
		type string;
	    }

	    uses ctrl:created-by-service;

	    leaf description {
		type string;
	    }

	    list device {
		key "device-name";

		leaf device-name {
		    type string;
		}

		leaf ip-address {
		    type inet:ip-prefix;
		}

		container static-route {
		    leaf destination {
			type inet:ip-prefix;
		    }

		    leaf next-hop {
			type inet:ip-address;
		    }
		}

		list interface {
		    key "interface-name";

		    leaf interface-name {
			type string;
		    }

		    leaf description {
			type string;
		    }

		    leaf vlan {
			type uint16;
		    }

		    leaf ip-address {
			type inet:ipv4-address;
		    }

		    leaf rate {
			type uint32;
			units "Mbps";
		    }
		}
	    }
	}
    }
}
