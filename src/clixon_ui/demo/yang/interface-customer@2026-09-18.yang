module interface-customer {
    namespace "http://clicon.org/interface-customer";
    prefix ic;

    import ietf-inet-types { prefix inet; }
    import clixon-controller { prefix ctrl; }
    import bgp { prefix bgp; }

    revision "2026-09-18" {
        description "Add fec option to ether-options on customer interfaces.";
    }

    revision "2026-08-22" {
        description "Add testing flag, rewrites the service-id in the interface desc.";
    }

    revision "2026-08-21" {
        description "Add per-VLAN routing-instance (L3VPN).";
    }

    revision "2026-01-23" {
        description "Customer interface service.";
    }

    augment /ctrl:services {
        list interface-customer {
            key "service-name";
            description "Customer facing interfaces service";
            leaf service-name {
                type string;
            }

            leaf description {
                type string;
            }
            leaf bgp-customer {
                description "bgp-customer service";
                type leafref {
                    path "/ctrl:services/bgp:bgp-customer/bgp:service-name";
                }
            }
            leaf testing {
                description "Put every serviceID in this instance in testing, rewrites the service-id in the interface desc from SU-S to SU-X so that monitoring, which matches ^SU-S in the desc, does not alarm on it. Can be overridden per serviceID";
                type boolean;
                default false;
            }
            uses ctrl:created-by-service;

            list serviceID {
                key "service-id zinotag";
                leaf service-id {
                    type string;
                    must "count(/ctrl:services/ic:interface-customer/ic:serviceID[ic:service-id = current()]) = 1" {
                        error-message "service-id must be globally unique.";
                    }
                }
                leaf description {
                    type string;
                }
                leaf zinotag {
                    type string;
                    description "zinotag that will be added in the interface desc";
                    must "count(/ctrl:services/ic:interface-customer/ic:serviceID[ic:zinotag = current()]) = 1" {
                        error-message "zinotag must be globally unique.";
                    }
                }
                leaf testing {
                    description "Testing for this serviceID only, keeps it out of monitoring while the rest of the instance stays in production. Overrides the instance level flag, left unset the instance level flag is used. No default on purpose, unset must stay distinguishable from an explicit false";
                    type boolean;
                }
                list static-route {
                    key "destination";

                    leaf description {
                        type string;
                    }
                    leaf routing-instance {
                        type string;
                    }
                    leaf destination {
                        type inet:ip-prefix;
                    }

                    leaf next-hop {
                        type inet:ip-address;
                    }
                }
                container device {
                    description "Connected router";
                    leaf name {
                        description "Connected router";
                        type leafref {
                            path "/ctrl:devices/ctrl:device/ctrl:name";
                            require-instance false;
                        }
                    }
                    list interface {
                        key "interface-name";

                        leaf interface-name {
                            type string;
                        }
                        leaf description {
                            type string;
                        }
                        leaf zinotag {
                            type string;
                            description "zinotag physical interface";
                        }
                        leaf mtu {
                            type uint16;
                        }
                        leaf rate {
                            description "Not implemented yet.";
                            type uint32;
                            units "Mbps";
                        }
                        leaf auto-neg {
                            description "auto-negotiation";
                            type enumeration {
                                enum no-auto-neg;
                            }
                        }
                        leaf speed {
                            description "Interface speed";
                            type enumeration {
                                enum 1g;
                                enum 10g;
                                enum 25g;
                                enum 40g;
                                enum 100g;
                            }
                        }
                        leaf flow-control {
                            description "no-flow-control";
                            type enumeration {
                                enum no-flow-control;
                            }
                        }
                        leaf fec {
                            description "Forward error correction";
                            type enumeration {
                                enum fec74;
                                enum fec91;
                            }
                        }
                        leaf-list input-filter-ipv4 {
                            description "IPv4 input filters to be applied to the interface";
                            type string;
                            ordered-by user;
                        }
                        leaf-list input-filter-ipv6 {
                            description "IPv6 input filters to be applied to the interface";
                            type string;
                            ordered-by user;
                        }
                        leaf-list output-filter-ipv4 {
                            description "IPv4 output filters to be applied to the interface";
                            type string;
                            ordered-by user;
                        }
                        leaf-list output-filter-ipv6 {
                            description "IPv6 output filters to be applied to the interface";
                            type string;
                            ordered-by user;
                        }
                        choice vlan-config {
                            description "Configuration for VLAN or no VLAN";
                            case no-vlan {
                                description "Interface without VLAN";
                                leaf description {
                                    type string;
                                }
                                leaf service-id {
                                    type string;
                                }
                                leaf zinotag {
                                    type string;
                                    description "zinotag that will be added in the interface desc";
                                }
                                leaf bgp-customer {
                                    description "bgp-customer service created rpf filter";
                                    type leafref {
                                        path "/ctrl:services/bgp:bgp-customer/bgp:service-name";
                                    }
                                }
                                choice addr-or-encap {
                                    description "Must choose either IPs (at least one of v4 or v6) or encapsulation";
                                    case addresses {
                                        leaf-list ip-address {
                                            type inet:ipv4-prefix;
                                            //unique;
                                        }
                                        leaf-list ipv6-address {
                                            type inet:ipv6-prefix;
                                            //unique;
                                        }
                                    }
                                    case encapsulation {
                                        leaf encapsulation {
                                            type enumeration {
                                                enum ethernet-ccc;
                                            }
                                        }
                                    }
                                }
                            }
                            case with-vlans {
                                description "Interface with VLANs";
                                container vlans {
                                    list vlan {
                                        key "vlan-id";
                                        description "One or more VLANs, each requiring either IPs or encapsulation";
                                        leaf vlan-id {
                                            description "VLAN ID, also creates unit with the same number";
                                            type uint16;
                                        }
                                        leaf description {
                                            type string;
                                        }
                                        leaf service-id {
                                            type string;
                                        }
                                        leaf core {
                                            description "Core interface add iso and mpls familys";
                                            type boolean;
                                        }
                                        leaf zinotag {
                                            type string;
                                            description "zinotag that will be added in the interface desc";
                                        }
                                        leaf bgp-customer {
                                            description "bgp-customer service created rpf filter";
                                            type leafref {
                                                path "/ctrl:services/bgp:bgp-customer/bgp:service-name";
                                            }
                                        }
                                        leaf routing-instance {
                                            description "Existing routing-instance (VRF) on the device that the unit is placed in, also marks the interface desc as EXT:L3VPN";
                                            type string;
                                            must "not(../encapsulation)" {
                                                error-message "routing-instance cannot be combined with encapsulation.";
                                            }
                                        }
                                        choice addr-or-encap {
                                            description "Must choose either IPs (at least one of v4 or v6) or encapsulation";
                                            case addresses {
                                                leaf-list ip-address {
                                                    type inet:ipv4-prefix;
                                                    //unique;
                                                }
                                                leaf-list ipv6-address {
                                                    type inet:ipv6-prefix;
                                                    //unique;
                                                }
                                            }
                                            case encapsulation {
                                                leaf encapsulation {
                                                    type enumeration {
                                                        enum vlan-ccc;
                                                    }
                                                }
                                            }
                                        }
                                    }
                                    must "count(vlan) > 0" {
                                        error-message "At least one VLAN must be defined.";
                                    }
                                }
                            }
                        }
                    }
                }
            }
        }
    }
}
