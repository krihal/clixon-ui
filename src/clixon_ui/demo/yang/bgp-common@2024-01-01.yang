submodule bgp-common {
    belongs-to bgp {
	prefix bgp;
    }

    revision "2024-01-01" {
	description "Initial revision.";
    }

    // currently only used be peer, should be used by customer in long-term (or just be ripped out of peer)
    grouping teardown {
	leaf teardown-limit-threshold {
	    description "Percentage of prefix-limit to start warnings";
	    type uint32 { range "1..100"; }
	    default 80;
	}
	leaf teardown-idle-timeout {
	    description "Timeout before attempting to restart peer";
	    type uint32 { range "1..2400"; }
	    default 60;
	}
    }

    // database inlined in peer, as it doesn't allow global source
    grouping irr {
	leaf irr-database {
	    description "Internet Routing Registry database host (e.g., whois.radb.net or rr.ntt.net)";
	    type string;
	}

	leaf-list irr-sources {
	    description "Source database to filter for in IRR lookup (e.g., RIPE, APNIC, RADB)";
	    type string;
	}
    }

}
