module clicon-ssh-users {
    namespace "http://clicon.org/ssh-users";
    prefix ssh-users;

    import ietf-inet-types { prefix inet; }
    import clixon-controller { prefix ctrl; }

    revision 2025-09-19{
	description "SSH users";
    }

    augment "/ctrl:services" {
	list ssh-users {
	    key service-name;

	    leaf service-name {
		type string;
		description "User group";
	    }

	    description "Users service";
	    
	    leaf-list devices {
		type string;
		description "Devices to create the users on, if left empty create on all devices";
		min-elements 0;
	    }

	    leaf-list device-groups {
		description "Device groups to create the users on";
		type leafref {
		    path "/ctrl:devices/ctrl:device-group/ctrl:name";
		}
		min-elements 0;
	    }

	    list user {
		key name;
		leaf name {
		    type string;
		    description "User name";
		}

		leaf full-name {
		    type string;
		    description "Full name of user";
		}

		leaf-list ssh-key {
		    type string;
			description "SSH public keys for the user";
		}

		leaf class {
		    type string;
		}
	    }

	    uses ctrl:created-by-service;
	    
	}
    }
}
