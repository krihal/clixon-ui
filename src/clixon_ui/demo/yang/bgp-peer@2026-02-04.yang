submodule bgp-peer {
    belongs-to bgp {
	prefix bgp;
    }

    import ietf-inet-types { prefix inet;  }
    import clixon-controller { prefix ctrl; }

    include bgp-common;

    revision "2026-02-04" {
		description "BGP peering.";
    }

    grouping naming-settings {
    	leaf prefix {
			type string;
		}
		leaf attribute {
			type enumeration {
			    enum as-macro-upper-case;
			    enum as-macro-lower-case;
			    enum service-name;
			    enum as-name-lower-case;
			}
		}
		leaf postfix {
			type string;
		}
    }

    grouping bgp-peer-settings {
	leaf description  { type string; }
	leaf as-macro4    { type string; }
	leaf as-macro6    { type string; }
	leaf md5-sum      { type string; }

	leaf prefix-limit  { type uint32 { range "1..max"; } }
	leaf prefix6-limit { type uint32 { range "1..max"; } }
    }

    augment /ctrl:services {
	list bgp-peer {
	    key service-name;

	    leaf service-name {
		type string;
	    }

	    uses ctrl:created-by-service;

	    leaf as-number {
		type inet:as-number;
		mandatory true;
	    }

	    leaf-list irr-sources {
		type string;
	    }

	    leaf auto-update {
		type boolean;
		default false;
	    }

	    leaf-list import-rules {
		description "Import rules for peering";
		type string;
		ordered-by user;
	    }

	    leaf-list export-rules {
		description "Export rules for peering";
		type string;
		ordered-by user;
	    }

	    leaf-list as-list {
		description "AS Numbers manually added to the filter";
		type inet:as-number;
		ordered-by user;
	    }

        leaf disable {
            description "Disable/enable peering for this service";
            type boolean;
            default false;
        }

	    uses bgp-peer-settings;

	    list exchange-points {
		key exchange-point;

		leaf exchange-point {
			description "Exchange point to peer on";
			type leafref {
				path "/ctrl:services/ctrl:properties/bgp:bgp-peer/bgp:exchange-points/bgp:name";
			}
		}

		leaf as-number {
		    description "Local AS number for this IX (overrides the service AS)";
		    type inet:as-number;
		}

		leaf md5-sum {
		    description "Local MD5 sum for this IX (overrides the service md5-sum)";
		    type string;
		}

		leaf-list import-rules {
		    description "Import rules for peering";
		    type string;
		    ordered-by user;
		}

		leaf-list export-rules {
		    description "Export rules for peering";
		    type string;
		    ordered-by user;
		}

		list peering {
		    key ip;
		    leaf ip {
			description "Neighbor IP address(es) for peering";
			type inet:ip-address;
		    }

		    leaf md5-sum {
			description "MD5 sum for the specific peering session (overrides the service and ix md5-sum)";
			type string;
		    }

		    leaf as-number {
			description "Local AS number for this peering (overrides the IX AS)";
			type inet:as-number;
		    }

		    leaf-list import-rules {
			description "Import rules for peering";
			type string;
			ordered-by user;
		    }

		    leaf-list export-rules {
			description "Export rules for peering";
			type string;
			ordered-by user;
		    }
		}
	    }
	}
    }

    // Properties
    augment /ctrl:services/properties {
	container bgp-peer {
		container naming {
			container as-path-group-name {
				uses naming-settings;
			}
			container policy-statement-term {
				uses naming-settings;
			}
			container policy-statement-name {
				uses naming-settings;
			}
		}

	    list exchange-points {

		key name;
		leaf name { type string; }

		leaf routing-instance {
		    description "Place neighbor entries for this IX under a certain routing-instance";
		    type string;
		}

		list router {
		    // there should be at least one of these, but I cannot get the must count to work
		    key name;
		    leaf name {
			description "Router at this exchange point";
			type leafref {
			path "/ctrl:devices/ctrl:device/ctrl:name";
			}
			mandatory true;
		    }
		    leaf logical-system {
			description "Logical system to create the peer in (JunOS only).";
			type string;
		    }
		    leaf-list prefixes {
			description "Prefixes used at this IX.";
			type inet:ip-prefix;
		    }
		}

		leaf-list aliases {
		    description "Alternative names for the exchange point";
		    type string;
		}

		leaf-list import-rules {
		    description "Policies for the exchange point.";
		    type string;
		    ordered-by user;
		}

	    }

	    uses teardown;

	    leaf irr-database {
		description "Internet Routing Registry database host (e.g., whois.radb.net or rr.ntt.net)";
		type string;
	    }

	    leaf as-filter-delta-limit {
		description "Percentage limit for maximum automated AS filter update";
		type uint8;
		default 15;
	    }
	}
    }

}
