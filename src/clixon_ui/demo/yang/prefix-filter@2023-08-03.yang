module prefix-filter {
    namespace "http://nordu.net/ns/clixon/prefix-filter";
    prefix prefix-filter;

    import ietf-inet-types { prefix inet; }
    import ietf-yang-types { prefix ietf; }
    import clixon-controller { prefix ctrl; }

    revision 2023-08-03{
	description "Initial prototype";
    }

    typedef ip-version {
	type enumeration {
	    enum ipv4;
	    enum ipv6;
	}
    }

    augment "/ctrl:services" {
	list prefix-filter {
	    key service-name;

	    leaf service-name {
		type string;
	    }

	    description "Prefix filter service";

	    leaf filter-name {
		description "Name the filter will have on the devices";
		type string;
		mandatory true;
	    }

	    leaf ip-version {
		description "IP version for the filter";
		type ip-version;
		mandatory true;
	    }

	    leaf as-macro {
		type string;
		description "AS Macro to generate prefix-filter from";
	    }

	    leaf-list manual-prefixes {
		description "Manually added IP prefixes";
		type inet:ip-prefix;
	    }

	    leaf-list irr-sources {
		description "Source IRR for filter data (e.g., RIPE, APNIC, RADB)";
		type string;
	    }

	    leaf irr-host {
		type string;
		description "Host used for bgpq query";

		default "rr.ntt.net";
	    }

	    leaf-list devices {
		description "Device to create the filter on";
		type leafref {
		    path "/ctrl:devices/ctrl:device/ctrl:name";
		}
		min-elements 0;
	    }

	    leaf-list device-groups {
		description "Device groups to create the filter on";
		type leafref {
		    path "/ctrl:devices/ctrl:device-group/ctrl:name";
		}
		min-elements 0;
	    }

	    leaf auto-update {
		type boolean;
		default true;
	    }

	    uses ctrl:created-by-service;
	}
    }
}
