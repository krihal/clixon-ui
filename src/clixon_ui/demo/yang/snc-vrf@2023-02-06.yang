module snc-vrf {

    namespace "http://sunet.se/snc/vrf";
    prefix vrf;

    import ietf-inet-types { prefix inet; }
    import ietf-yang-types { prefix ietf; }
    import clixon-controller { prefix ctrl; }

    revision 2023-02-06{
        description "Initial prototype";
    }

    // maybe put this in library
    grouping ndn-service-id {
        leaf service-id {
            type string;
            description "Unique Service ID, auto-assigned if not set";
        }
    }

    grouping reject-or-receive {
        choice reject-or-receive-choice {
            case accept {
                leaf accept {
                    type empty;
                }
            }
            case reject {
                leaf reject {
                    type empty;
                }
            }
            mandatory true;
            description "Accept or reject the route, mandatory";
        }
    }

    grouping routing-options {
        container routing-options {
            choice routing-choice {
                case static-route {
                    container static-route {
                        leaf route {
                            type inet:ip-prefix;
                            mandatory true;
                        }
                        uses reject-or-receive;
                        leaf preference {
                            type uint32;
                        }
                    }
                }
                // more cases
            }
            description "Routing options for the VRF, optional";
        }
    }

    grouping protocol-options {
        container protocol-options {
            choice protocol-choice {
                case ospf {
                    leaf ospf {
                        type empty;
                    }
                }
                // more cases
            }
            description "Protocol options for the VRF, optional";
        }
    }

    // probably overly simple, but we start with it
    typedef policy {
        type enumeration {
            enum accept-bgp;
        }
        description "Policy for the VRF VRF, must be set if a protocol option is set";
    }

    // service
    augment "/ctrl:services" {
        list vrf {
            description "VRF Service";
            key service-name;
            leaf service-name {
                type string;
            }

            // service options

            uses ndn-service-id;

            leaf description {
                type string;
                description "Description of the VRF, optional";
            }

            leaf vrf-target {
                type string;
                description "Unique community target for the VRF, auto-assigned if not set";
            }

            leaf vrf-table-label {
                type empty;
                description "If vrf-table-lable should be set for the VRF, optional";
            }

            list devices {

                key device;
                leaf device {
                    description "Device to create the VRF on";
                    type leafref {
                        path "/ctrl:devices/ctrl:device/ctrl:name";
                    }
                }

                list interfaces {

                    key interface;
                    leaf interface {
                        type string;
                        description "Interfaces to add to the VRF, mandatory";
                    }
                }
                description "Devices to create the VRF on, mandatory";
            }

            uses routing-options;
            uses protocol-options;

            container policy-options {
                leaf policy {
                    type policy;
                }
                description "Policy to create for the VRF, optional";
            }

//            uses vrf-register-service;
//            uses vrf-update-service;

        }
    }

}
